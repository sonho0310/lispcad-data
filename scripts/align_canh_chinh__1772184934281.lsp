;;; ===============================================================
;;; ALIGN & DISTRIBUTE
;;; ===============================================================
;;; 
;;; A. ALIGN (CAN CHINH - THEO DOI TUONG MOC)
;;;    ALL : Can Trai (Align Left)
;;;    ALR : Can Phai (Align Right)
;;;    ALT : Can Tren (Align Top)
;;;    ALB : Can Duoi (Align Bottom)
;;;    ALX : Can Giua X (Align Mid X - Truc doc)
;;;    ALY : Can Giua Y (Align Mid Y - Truc ngang)
;;;
;;; B. DISTRIBUTE AUTO (CHIA DEU TU DONG)
;;;    DTX : Dan deu X (Giu dau/cuoi, chia deu o giua)
;;;    DTY : Dan deu Y (Giu dau/cuoi, chia deu o giua)
;;;
;;; C. DISTRIBUTE SMART (DAN THEO KHOANG CACH NHAP - TU DONG HUONG)
;;;    DDX : Dan deu X (Tu dong check Trai/Phai so voi Moc)
;;;    DDY : Dan deu Y (Tu dong check Tren/Duoi so voi Moc)
;;; ===============================================================

(vl-load-com)

;;; --- HÀM HỖ TRỢ ---

(defun Get-Bounding-Box (obj / minpt maxpt)
  (vla-getboundingbox obj 'minpt 'maxpt)
  (list (vlax-safearray->list minpt) (vlax-safearray->list maxpt))
)

(defun Get-Center (obj / bb p1 p2)
  (setq bb (Get-Bounding-Box obj))
  (setq p1 (car bb) p2 (cadr bb))
  (list (/ (+ (car p1) (car p2)) 2.0)    
        (/ (+ (cadr p1) (cadr p2)) 2.0)  
        (/ (+ (caddr p1) (caddr p2)) 2.0)) 
)

(defun Move-Obj (obj vec)
  (vla-move obj (vlax-3d-point '(0 0 0)) (vlax-3d-point vec))
)

;;; ===============================================================
;;; PHẦN 1: ALIGN (CAN CHINH THEO MOC)
;;; ===============================================================
;; Name: Căn Trái (Align Left)
;; Desc: Lệnh ALL - Căn các đối tượng theo bên trái của Mốc
(defun c:ALL (/ entAnchor objAnchor targetX ss i obj)
  (setq entAnchor (car (entsel "\n[Align LEFT] Chon doi tuong MOC: ")))
  (if entAnchor (progn
      (setq objAnchor (vlax-ename->vla-object entAnchor))
      (setq targetX (car (car (Get-Bounding-Box objAnchor))))
      (prompt "\nChon cac doi tuong can di chuyen:")
      (setq ss (ssget))
      (if ss (progn (vla-startundomark (vla-get-activedocument (vlax-get-acad-object)))
          (repeat (setq i (sslength ss))
            (setq obj (vlax-ename->vla-object (ssname ss (setq i (1- i)))))
            (if (not (equal obj objAnchor))
                (Move-Obj obj (list (- targetX (car (car (Get-Bounding-Box obj)))) 0 0)))
          )(vla-endundomark (vla-get-activedocument (vlax-get-acad-object)))
      ))
  )) (princ)
)
;; Name: Căn Phải (Align Right)
;; Desc: Lệnh ALR - Căn các đối tượng theo bên phải của Mốc
(defun c:ALR (/ entAnchor objAnchor targetX ss i obj)
  (setq entAnchor (car (entsel "\n[Align RIGHT] Chon doi tuong MOC: ")))
  (if entAnchor (progn
      (setq objAnchor (vlax-ename->vla-object entAnchor))
      (setq targetX (car (cadr (Get-Bounding-Box objAnchor))))
      (prompt "\nChon cac doi tuong can di chuyen:")
      (setq ss (ssget))
      (if ss (progn (vla-startundomark (vla-get-activedocument (vlax-get-acad-object)))
          (repeat (setq i (sslength ss))
            (setq obj (vlax-ename->vla-object (ssname ss (setq i (1- i)))))
            (if (not (equal obj objAnchor))
                (Move-Obj obj (list (- targetX (car (cadr (Get-Bounding-Box obj)))) 0 0)))
          )(vla-endundomark (vla-get-activedocument (vlax-get-acad-object)))
      ))
  )) (princ)
)
;; Name: Căn Đỉnh (Align Top)
;; Desc: Lệnh ALT - Căn các đối tượng theo đỉnh trên của Mốc
(defun c:ALT (/ entAnchor objAnchor targetY ss i obj)
  (setq entAnchor (car (entsel "\n[Align TOP] Chon doi tuong MOC: ")))
  (if entAnchor (progn
      (setq objAnchor (vlax-ename->vla-object entAnchor))
      (setq targetY (cadr (cadr (Get-Bounding-Box objAnchor))))
      (prompt "\nChon cac doi tuong can di chuyen:")
      (setq ss (ssget))
      (if ss (progn (vla-startundomark (vla-get-activedocument (vlax-get-acad-object)))
          (repeat (setq i (sslength ss))
            (setq obj (vlax-ename->vla-object (ssname ss (setq i (1- i)))))
            (if (not (equal obj objAnchor))
                (Move-Obj obj (list 0 (- targetY (cadr (cadr (Get-Bounding-Box obj)))) 0)))
          )(vla-endundomark (vla-get-activedocument (vlax-get-acad-object)))
      ))
  )) (princ)
)
;; Name: Căn Đáy (Align Bottom)
;; Desc: Lệnh ALB - Căn các đối tượng theo đáy dưới của Mốc
(defun c:ALB (/ entAnchor objAnchor targetY ss i obj)
  (setq entAnchor (car (entsel "\n[Align BOTTOM] Chon doi tuong MOC: ")))
  (if entAnchor (progn
      (setq objAnchor (vlax-ename->vla-object entAnchor))
      (setq targetY (cadr (car (Get-Bounding-Box objAnchor))))
      (prompt "\nChon cac doi tuong can di chuyen:")
      (setq ss (ssget))
      (if ss (progn (vla-startundomark (vla-get-activedocument (vlax-get-acad-object)))
          (repeat (setq i (sslength ss))
            (setq obj (vlax-ename->vla-object (ssname ss (setq i (1- i)))))
            (if (not (equal obj objAnchor))
                (Move-Obj obj (list 0 (- targetY (cadr (car (Get-Bounding-Box obj)))) 0)))
          )(vla-endundomark (vla-get-activedocument (vlax-get-acad-object)))
      ))
  )) (princ)
)
;; Name: Căn Giữa Dọc (Mid X)
;; Desc: Lệnh ALX - Căn giữa theo trục đứng
(defun c:ALX (/ entAnchor objAnchor centerAnchor targetX ss i obj)
  (setq entAnchor (car (entsel "\n[Align Mid X] Chon doi tuong MOC: ")))
  (if entAnchor (progn
      (setq objAnchor (vlax-ename->vla-object entAnchor))
      (setq targetX (car (Get-Center objAnchor)))
      (prompt "\nChon cac doi tuong can di chuyen:")
      (setq ss (ssget))
      (if ss (progn (vla-startundomark (vla-get-activedocument (vlax-get-acad-object)))
          (repeat (setq i (sslength ss))
            (setq obj (vlax-ename->vla-object (ssname ss (setq i (1- i)))))
            (if (not (equal obj objAnchor))
                (Move-Obj obj (list (- targetX (car (Get-Center obj))) 0 0)))
          )(vla-endundomark (vla-get-activedocument (vlax-get-acad-object)))
      ))
  )) (princ)
)
;; Name: Căn Giữa Ngang (Mid Y)
;; Desc: Lệnh ALY - Căn giữa theo trục ngang
(defun c:ALY (/ entAnchor objAnchor centerAnchor targetY ss i obj)
  (setq entAnchor (car (entsel "\n[Align Mid Y] Chon doi tuong MOC: ")))
  (if entAnchor (progn
      (setq objAnchor (vlax-ename->vla-object entAnchor))
      (setq targetY (cadr (Get-Center objAnchor)))
      (prompt "\nChon cac doi tuong can di chuyen:")
      (setq ss (ssget))
      (if ss (progn (vla-startundomark (vla-get-activedocument (vlax-get-acad-object)))
          (repeat (setq i (sslength ss))
            (setq obj (vlax-ename->vla-object (ssname ss (setq i (1- i)))))
            (if (not (equal obj objAnchor))
                (Move-Obj obj (list 0 (- targetY (cadr (Get-Center obj))) 0)))
          )(vla-endundomark (vla-get-activedocument (vlax-get-acad-object)))
      ))
  )) (princ)
)

;;; ===============================================================
;;; PHẦN 2: DISTRIBUTE AUTO (CHIA DEU TU DONG DAU-CUOI)
;;; ===============================================================
;; Name: Dàn Đều Ngang (Auto)
;; Desc: Lệnh DTX - Chia đều khoảng cách theo phương ngang (giữ đầu cuối)
(defun c:DTX (/ ss lst i obj center minX maxX step currentX sortedLst cnt)
  (prompt "\n[Distribute X Auto] Chon >= 3 doi tuong:")
  (setq ss (ssget))
  (if (and ss (> (sslength ss) 2)) (progn
      (vla-startundomark (vla-get-activedocument (vlax-get-acad-object)))
      (setq lst '())
      (repeat (setq i (sslength ss))
        (setq obj (vlax-ename->vla-object (ssname ss (setq i (1- i)))))
        (setq center (Get-Center obj))
        (setq lst (cons (list (car center) obj) lst))
      )
      (setq sortedLst (vl-sort lst '(lambda (a b) (< (car a) (car b)))))
      (setq cnt (length sortedLst))
      (setq minX (caar sortedLst) maxX (car (last sortedLst)))
      (setq step (/ (- maxX minX) (float (- cnt 1))))
      (setq i 0)
      (foreach item sortedLst
        (setq obj (cadr item) currentX (car item))
        (Move-Obj obj (list (- (+ minX (* i step)) currentX) 0 0))
        (setq i (1+ i))
      )
      (vla-endundomark (vla-get-activedocument (vlax-get-acad-object)))
  )) (princ)
)
;; Name: Dàn Đều Dọc (Auto)
;; Desc: Lệnh DTY - Chia đều khoảng cách theo phương dọc (giữ đầu cuối)
(defun c:DTY (/ ss lst i obj center minY maxY step currentY sortedLst cnt)
  (prompt "\n[Distribute Y Auto] Chon >= 3 doi tuong:")
  (setq ss (ssget))
  (if (and ss (> (sslength ss) 2)) (progn
      (vla-startundomark (vla-get-activedocument (vlax-get-acad-object)))
      (setq lst '())
      (repeat (setq i (sslength ss))
        (setq obj (vlax-ename->vla-object (ssname ss (setq i (1- i)))))
        (setq center (Get-Center obj))
        (setq lst (cons (list (cadr center) obj) lst))
      )
      (setq sortedLst (vl-sort lst '(lambda (a b) (< (car a) (car b)))))
      (setq cnt (length sortedLst))
      (setq minY (caar sortedLst) maxY (car (last sortedLst)))
      (setq step (/ (- maxY minY) (float (- cnt 1))))
      (setq i 0)
      (foreach item sortedLst
        (setq obj (cadr item) currentY (car item))
        (Move-Obj obj (list 0 (- (+ minY (* i step)) currentY) 0))
        (setq i (1+ i))
      )
      (vla-endundomark (vla-get-activedocument (vlax-get-acad-object)))
  )) (princ)
)

;;; ===============================================================
;;; PHẦN 3: DISTRIBUTE SMART (TU DONG DOI HUONG)
;;; ===============================================================
;; Name: Dàn Đều Ngang (Smart)
;; Desc: Lệnh DDX - Dàn đều sang trái/phải theo khoảng cách nhập vào
;;; --- DDX : Tu dong check Trai hay Phai so voi Moc ---
(defun c:DDX (/ entAnchor objAnchor startX lst i obj center dist sortedLst currentX targetX sumX avgX direction)
  (setq entAnchor (car (entsel "\n[Distribute Smart X] Chon doi tuong MOC: ")))
  (if entAnchor (progn
      (setq objAnchor (vlax-ename->vla-object entAnchor))
      (setq startX (car (Get-Center objAnchor)))
      (prompt "\nChon cac doi tuong con lai:")
      (setq ss (ssget))
      (if ss (progn
           (setq dist (getdist "\nNhap khoang cach (Distance X): "))
           (if dist (progn
                (vla-startundomark (vla-get-activedocument (vlax-get-acad-object)))
                (setq lst '() sumX 0.0)
                (repeat (setq i (sslength ss))
                  (setq obj (vlax-ename->vla-object (ssname ss (setq i (1- i)))))
                  (if (not (equal obj objAnchor)) (progn
                        (setq center (Get-Center obj))
                        (setq sumX (+ sumX (car center)))
                        (setq lst (cons (list (car center) obj) lst))
                  ))
                )
                ;; Tinh trung binh cong X de biet nam ben trai hay phai
                (setq avgX (/ sumX (length lst)))
                (if (> avgX startX)
                    (progn ; Ben PHAI Moc -> Sap xep tang dan, huong duong
                        (setq direction 1.0)
                        (setq sortedLst (vl-sort lst '(lambda (a b) (< (car a) (car b)))))
                    )
                    (progn ; Ben TRAI Moc -> Sap xep giam dan, huong am
                        (setq direction -1.0)
                        (setq sortedLst (vl-sort lst '(lambda (a b) (> (car a) (car b)))))
                    )
                )
                ;; Thuc hien di chuyen
                (setq i 1)
                (foreach item sortedLst
                   (setq obj (cadr item))
                   (setq currentX (car item))
                   (setq targetX (+ startX (* i dist direction)))
                   (Move-Obj obj (list (- targetX currentX) 0 0))
                   (setq i (1+ i))
                )
                (vla-endundomark (vla-get-activedocument (vlax-get-acad-object)))
                (princ (strcat "\nDa dan deu huong " (if (> direction 0) "PHAI" "TRAI")))
             ))
      ))
  )) (princ)
)
;; Name: Dàn Đều Dọc (Smart)
;; Desc: Lệnh DDY - Dàn đều lên trên/dưới theo khoảng cách nhập vào
;;; --- DDY : Tu dong check Tren hay Duoi so voi Moc ---
(defun c:DDY (/ entAnchor objAnchor startY lst i obj center dist sortedLst currentY targetY sumY avgY direction)
  (setq entAnchor (car (entsel "\n[Distribute Smart Y] Chon doi tuong MOC: ")))
  (if entAnchor (progn
      (setq objAnchor (vlax-ename->vla-object entAnchor))
      (setq startY (cadr (Get-Center objAnchor)))
      (prompt "\nChon cac doi tuong con lai:")
      (setq ss (ssget))
      (if ss (progn
           (setq dist (getdist "\nNhap khoang cach (Distance Y): "))
           (if dist (progn
                (vla-startundomark (vla-get-activedocument (vlax-get-acad-object)))
                (setq lst '() sumY 0.0)
                (repeat (setq i (sslength ss))
                  (setq obj (vlax-ename->vla-object (ssname ss (setq i (1- i)))))
                  (if (not (equal obj objAnchor)) (progn
                        (setq center (Get-Center obj))
                        (setq sumY (+ sumY (cadr center)))
                        (setq lst (cons (list (cadr center) obj) lst))
                  ))
                )
                ;; Tinh trung binh cong Y
                (setq avgY (/ sumY (length lst)))
                (if (> avgY startY)
                    (progn ; Ben TREN Moc -> Sap xep tang dan (duoi len tren), huong duong
                        (setq direction 1.0)
                        (setq sortedLst (vl-sort lst '(lambda (a b) (< (car a) (car b)))))
                    )
                    (progn ; Ben DUOI Moc -> Sap xep giam dan (tren xuong duoi), huong am
                        (setq direction -1.0)
                        (setq sortedLst (vl-sort lst '(lambda (a b) (> (car a) (car b)))))
                    )
                )
                (setq i 1)
                (foreach item sortedLst
                   (setq obj (cadr item))
                   (setq currentY (car item))
                   (setq targetY (+ startY (* i dist direction)))
                   (Move-Obj obj (list 0 (- targetY currentY) 0))
                   (setq i (1+ i))
                )
                (vla-endundomark (vla-get-activedocument (vlax-get-acad-object)))
                (princ (strcat "\nDa dan deu huong " (if (> direction 0) "LEN" "XUONG")))
             ))
      ))
  )) (princ)
)
